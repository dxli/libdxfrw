# Optional end-to-end nonzero-Z DWG -> dwg2dxf -> FreeCAD B-rep check.
#
# Generate the input from the checked-in local recipe, put this build's
# dwg2dxf directory first on PATH, and set LIBDXFRW_FREECAD_DWG to that DWG.
# Generated DWG/DXF outputs and the FreeCAD user configuration should remain
# outside the source tree. This is a generated consumer control, not an
# AutoCAD-authored interoperability witness.

import hashlib
import json
import os
import platform
import sys

import FreeCAD as App


sample = os.environ.get("LIBDXFRW_FREECAD_DWG")
if not sample or not os.path.isfile(sample):
    raise RuntimeError("LIBDXFRW_FREECAD_DWG must name an existing generated DWG")

draft_path = os.path.join(App.getResourceDir(), "Mod", "Draft")
sys.path.insert(0, draft_path)

import importDWG
import importDXF


legacy = App.ParamGet(
    "User parameter:BaseApp/Preferences/Mod/Draft"
).GetBool("dxfUseLegacyImporter", False)
if legacy:
    raise RuntimeError("This check requires FreeCAD's default C++ DXF importer")

captured = {}
original_convert = importDWG.convertToDxf
original_reporter = importDXF.DxfImportReporter


def capture_convert(filename):
    result = original_convert(filename)
    captured["dxf"] = result
    return result


class CapturingReporter(original_reporter):
    def __init__(self, filename, stats_dict, total_time=0.0):
        captured["stats"] = stats_dict
        super().__init__(filename, stats_dict, total_time)


def digest(path):
    sha = hashlib.sha256()
    with open(path, "rb") as stream:
        for chunk in iter(lambda: stream.read(1024 * 1024), b""):
            sha.update(chunk)
    return sha.hexdigest()


def close(actual, expected):
    return abs(actual - expected) < 1e-8


importDWG.convertToDxf = capture_convert
importDXF.DxfImportReporter = CapturingReporter

doc = None
try:
    doc = importDWG.open(sample)
    if doc is None:
        raise AssertionError("Draft.importDWG.open returned no document")

    dxf_path = captured.get("dxf")
    if not dxf_path or not os.path.isfile(dxf_path):
        raise AssertionError("Draft DWG conversion did not produce an auditable DXF")

    imported_edges = []
    imported_shapes = []
    for obj in doc.Objects:
        shape = getattr(obj, "Shape", None)
        if shape is None or shape.isNull():
            continue
        imported_shapes.append(shape)
        for edge in shape.Edges:
            points = [
                (vertex.Point.x, vertex.Point.y, vertex.Point.z)
                for vertex in edge.Vertexes
            ]
            imported_edges.append((obj.Name, edge, points))

    if len(imported_edges) != 1:
        raise AssertionError(
            "expected exactly one imported B-rep edge, got %d" % len(imported_edges)
        )
    if len(imported_edges[0][2]) != 2:
        raise AssertionError("expected the imported LINE edge to have two vertices")

    actual = sorted(imported_edges[0][2])
    expected = [(1.0, 2.0, 3.0), (4.0, 6.0, 9.0)]
    if any(
        not all(close(a, e) for a, e in zip(actual_point, expected_point))
        for actual_point, expected_point in zip(actual, expected)
    ):
        raise AssertionError(
            "FreeCAD LINE endpoint mismatch: expected %r, got %r" % (expected, actual)
        )
    if not all(point[2] != 0.0 for point in actual):
        raise AssertionError("FreeCAD import flattened the LINE's nonzero Z endpoints")
    if not all(shape.isValid() for shape in imported_shapes):
        raise AssertionError("FreeCAD produced an invalid B-rep shape")

    stats = captured.get("stats") or {}
    entity_counts = stats.get("entityCounts", {})
    if entity_counts.get("LINE", 0) != 1:
        raise AssertionError("FreeCAD did not report exactly one LINE: %r" % entity_counts)
    unsupported = stats.get("unsupportedFeatures", {})
    if unsupported.get("LINE"):
        raise AssertionError("FreeCAD reported the LINE as unsupported: %r" % unsupported)

    preferences = App.ParamGet("User parameter:BaseApp/Preferences/Mod/Draft")
    result = {
        "status": "pass",
        "freecad_version": list(App.Version()),
        "platform": platform.platform(),
        "architecture": platform.machine(),
        "importer": "C++",
        "import_mode": preferences.GetInt("DxfImportMode", 2),
        "converter": importDWG.get_libredwg_converter("dwg2dxf"),
        "source": os.path.basename(sample),
        "source_sha256": digest(sample),
        "dxf_size": os.path.getsize(dxf_path),
        "dxf_sha256": digest(dxf_path),
        "line_count": entity_counts.get("LINE"),
        "unsupported_features": {
            key: len(values) for key, values in sorted(unsupported.items())
        },
        "edge_endpoints": actual,
        "edge_count": len(imported_edges),
    }
    print("FREECAD_DWG2DXF_3D_LINE_ASSERTIONS_PASS=" + json.dumps(result, sort_keys=True))
finally:
    if doc is not None and doc.Name in App.listDocuments():
        App.closeDocument(doc.Name)
