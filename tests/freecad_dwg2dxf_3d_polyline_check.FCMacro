# Optional end-to-end 3D POLYLINE DWG -> dwg2dxf -> FreeCAD B-rep check.
#
# Generate the input from the checked-in local recipe, put this build's
# dwg2dxf directory first on PATH, and set LIBDXFRW_FREECAD_DWG to that DWG.
# The generated DWG is a local control, not an AutoCAD-authored interoperability
# witness. Keep all generated files and FreeCAD configuration outside source.

import hashlib
import json
import os
import platform
import sys

import FreeCAD as App


sample = os.environ.get("LIBDXFRW_FREECAD_DWG")
if not sample or not os.path.isfile(sample):
    raise RuntimeError("LIBDXFRW_FREECAD_DWG must name an existing generated DWG")

draft_path = os.path.join(App.getResourceDir(), "Mod", "Draft")
sys.path.insert(0, draft_path)

import importDWG
import importDXF


legacy = App.ParamGet(
    "User parameter:BaseApp/Preferences/Mod/Draft"
).GetBool("dxfUseLegacyImporter", False)
if legacy:
    raise RuntimeError("This check requires FreeCAD's default C++ DXF importer")

captured = {}
original_convert = importDWG.convertToDxf
original_reporter = importDXF.DxfImportReporter


def capture_convert(filename):
    result = original_convert(filename)
    captured["dxf"] = result
    return result


class CapturingReporter(original_reporter):
    def __init__(self, filename, stats_dict, total_time=0.0):
        captured["stats"] = stats_dict
        super().__init__(filename, stats_dict, total_time)


def digest(path):
    sha = hashlib.sha256()
    with open(path, "rb") as stream:
        for chunk in iter(lambda: stream.read(1024 * 1024), b""):
            sha.update(chunk)
    return sha.hexdigest()


def close_point(actual, expected):
    return all(abs(a - e) < 1e-8 for a, e in zip(actual, expected))


def normalized_segment(points):
    if len(points) != 2:
        raise AssertionError("each 3D POLYLINE edge must have two endpoints")
    return tuple(sorted(points))


importDWG.convertToDxf = capture_convert
importDXF.DxfImportReporter = CapturingReporter

doc = None
try:
    doc = importDWG.open(sample)
    if doc is None:
        raise AssertionError("Draft.importDWG.open returned no document")

    dxf_path = captured.get("dxf")
    if not dxf_path or not os.path.isfile(dxf_path):
        raise AssertionError("Draft DWG conversion did not produce an auditable DXF")

    imported_edges = []
    imported_shapes = []
    for obj in doc.Objects:
        shape = getattr(obj, "Shape", None)
        if shape is None or shape.isNull():
            continue
        edges = list(shape.Edges)
        if not edges:
            continue
        imported_shapes.append(shape)
        for edge in edges:
            points = [
                (vertex.Point.x, vertex.Point.y, vertex.Point.z)
                for vertex in edge.Vertexes
            ]
            imported_edges.append(normalized_segment(points))

    expected_edges = sorted(
        [
            ((0.0, 0.0, 1.0), (2.0, 3.0, 4.0)),
            ((2.0, 3.0, 4.0), (5.0, 1.0, -2.0)),
        ]
    )
    if len(imported_shapes) != 1 or len(imported_edges) != len(expected_edges):
        raise AssertionError(
            "expected one imported shape with two edges; got %d shapes and %d edges"
            % (len(imported_shapes), len(imported_edges))
        )
    for actual_segment, expected_segment in zip(
        sorted(imported_edges), expected_edges
    ):
        if any(
            not close_point(actual, expected)
            for actual, expected in zip(actual_segment, expected_segment)
        ):
            raise AssertionError(
                "FreeCAD 3D POLYLINE edge mismatch: expected %r, got %r"
                % (expected_edges, imported_edges)
            )
    if not all(shape.isValid() for shape in imported_shapes):
        raise AssertionError("FreeCAD produced an invalid 3D POLYLINE B-rep")

    stats = captured.get("stats") or {}
    entity_counts = stats.get("entityCounts", {})
    if entity_counts.get("POLYLINE", 0) != 1:
        raise AssertionError(
            "FreeCAD did not report exactly one POLYLINE: %r" % entity_counts
        )
    unsupported = stats.get("unsupportedFeatures", {})
    if unsupported.get("POLYLINE"):
        raise AssertionError(
            "FreeCAD reported POLYLINE as unsupported: %r" % unsupported
        )

    preferences = App.ParamGet("User parameter:BaseApp/Preferences/Mod/Draft")
    result = {
        "status": "pass",
        "freecad_version": list(App.Version()),
        "platform": platform.platform(),
        "architecture": platform.machine(),
        "importer": "C++",
        "import_mode": preferences.GetInt("DxfImportMode", 2),
        "converter": importDWG.get_libredwg_converter("dwg2dxf"),
        "source": os.path.basename(sample),
        "source_sha256": digest(sample),
        "dxf_size": os.path.getsize(dxf_path),
        "dxf_sha256": digest(dxf_path),
        "polyline_count": entity_counts.get("POLYLINE"),
        "unsupported_features": {
            key: len(values) for key, values in sorted(unsupported.items())
        },
        "edges": sorted(imported_edges),
        "edge_count": len(imported_edges),
    }
    print(
        "FREECAD_DWG2DXF_3D_POLYLINE_ASSERTIONS_PASS="
        + json.dumps(result, sort_keys=True)
    )
finally:
    if doc is not None and doc.Name in App.listDocuments():
        App.closeDocument(doc.Name)
